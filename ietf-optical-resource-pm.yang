module ietf-optical-resource-pm {
  yang-version 1.1;
  namespace "urn:ietf:params:xml:ns:yang:ietf-optical-resource-pm";
  prefix optrpm;
  
  import ietf-yang-types {
    prefix "yang";
  }
  
  import ietf-optical-resource-pm-types {
    prefix "optrpm-types";
  }

    
  organization
    "IETF CCAMP Working Group";
    
  contact
    "WG Web:   <https://datatracker.ietf.org/wg/ccamp/>
     WG List:  <mailto:ccamp@ietf.org>

     Editor:   Chaode Yu
               <yuchaode@huawei.com>

     Editor:   Fabio Peruzzini
               <fabio.peruzzini@telecomitalia.it>

     Editor:   Yanlei Zheng
               <zhengyanlei@chinaunicom.cn>

     Editor:   Victor Lopez
               <victor.lopez@nokia.com>

     Editor:   Italo Busi
               <italo.busi@huawei.com>

     Editor:   Aihua Guo
               <aihuaguo.ietf@gmail.com>";
    
  description 
    "This module defines a model for optical performance 
    monitoring.

    The model fully conforms to the Network Management 
    Datastore Architecture (NMDA).
    
    Copyright (c) 2022 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";
 
    
  revision 2023-07-04 {
    description  "Initial revision.";
  }
  
  container performance-monitoring {
    description 
      "the root node.";
      
    uses monitoring-tasks-grouping;
    uses tca-management-grouping;
    uses resource-info-grouping;
  }
  
  grouping resource-info-grouping {
    description 
      "grouping of resources' PM capabilities related information";
    
    container resources {
      description
        "resources' PM capabilities related information";
        
      list resource-list {
        description
          "list of resource instances";
        key resource;
        
        leaf resource {
          type union {
            type instance-identifier {
              require-instance false;
            }
            type yang:object-identifier;
            type string;
           type yang:uuid;
          }
        }
        
        leaf resource-type {
          description 
            "the type of resource, such as NE, board or port";
        
          config false;
          type identityref {
            base optrpm-types:resource-type;
          }          
        }
        
        leaf holding-time {
          description 
            "Contains the time period in hours within which 24h PM 
            data records and 15min PM data records may be retrieved.
            If the domain controller does not store PM data it is the 
            time supported in the NE";
          
          type uint8;
          units "hour";
        }
        
        list pm-parameter-list {
          must "../optrpm:resource-type=optrpm-types:network-element";
          key "layer-rate";
          
          leaf layer-rate {
            description 
              "Layer rate of ME";
              
            type identityref {
              base optrpm-types:layer-rate-type;
            }
          }
          
          leaf-list indicator-name {
            type string;
          }
        }
        
        leaf-list sub-resources {
          description
            "the identifier of the performace monitoring point of this
            resource. If the resource is a NE, the sub-resource should
            be termination point. If the resource is a termination
            point contained in this NE, the sub-resource should be the
            logic channel on this TP";
            
          type leafref {
            path "../optrpm:resource";
          }          
        }
      }
    }
  }

  grouping monitoring-tasks-grouping {
    description 
      "grouping of performance monitoring task";
      
    container monitor-tasks {
      description
        "Information of PM tasks";
        
      list monitor-task {
        description 
          "monitoring task list";
          
        key task-id;
        uses task-instance-grouping;
      }
    }  
  }

  
  grouping task-instance-grouping {
    description 
      "grouping of performance monitoring task. In this monitoring
      task, the client can specify a resource to run a monitor task
      and what kind of performance data need to be monitored.";
    
    leaf task-id {
      description
        "identifier of the performance task";
      type yang:uuid;
    }
    
    leaf resource {
      description 
        "the identifier of network resource on which the performance
        monitoring task is running";
      
      type leafref {
        path "/optrpm:performance-monitoring/optrpm:resources" + 
        "/optrpm:resource-list/optrpm:resource";
      }
    }
    
    leaf resource-type {
      description 
        "the type of resource, such as NE, board or port";
        
      config false;
      type identityref {
        base optrpm-types:resource-type;
      }
    }
    
    leaf task-name {
      description 
        "the name of monitoring task";
        
      type string;
    }
    
    leaf admin-status {
      description
        "it is used to control enbling/disabling PM task";
    
      type enumeration {
        enum enabled {
          description
            "it is used to enable the pm task, if the task is enabled,
            the task-staus should be running";
        }
        
        enum disabled {
          description
            "it is used to disenable the pm task, if the task is 
            disabled, the task-staus should be suspended";
        }
      }
    }
    
    leaf task-status {
      config false;
      description 
        "the status of monitoring task.";
        
      type enumeration {
        enum running;
      
        enum suspended;
        
        enum abnormal;
      }
    }

    uses task-configuration-grouping;
  }
  
  grouping task-configuration-grouping {
    description
      "grouping of pm task configuration";
      
    container task-cfg {
      description 
        "Configuration of the monitoring task";
    
      leaf period {
        description 
          "it is used to indicate the interval as per monitoring
          task";
        type identityref {
          base optrpm-types:period;
        }
      }
      
      container indicators {
        description 
          "performance indicators";
          
        list indicator {
          description 
            "list of PM indicators to be monitored";
            
          key indicator-name;
          uses indicator-grouping;
        }
      }
    }  
  }
  
  grouping indicator-grouping {
    description 
      "grouping of a monitoring indicator instance";
      
    leaf indicator-name {
      description 
        "performance indicator's name";
        
      type string;
    }
    
    leaf indicator-value-unit {
      description 
        "unit of indicator value";
        
      type string;
    }
  }
  
  grouping tca-management-grouping {
    description 
      "grouping of configuration and management for Threshol Crossing
      Alert";
      
    container tca-management {
      description
        "configuration and management for Threshol Crossing Alert";
      
      container profiles {
        description
          "the TCA profile in the whole network";
      
        list profile {
          description
            "List of TCA profile instances";
            
          key "profile-id";          
          uses tca-profile-grouping;
        }
      }
    
      container tcas {
        description
          "TCA configuration on the network resources.";
          
        list tca {
          description
            "List of TCA configuration instances";
        
          key "resource";
        
          leaf resource {
            description 
              "the identifier of network resource on which threshold 
              is configured for TCA purpose";
          
            type leafref {
              path "/optrpm:performance-monitoring/optrpm:resources" + 
              "/optrpm:resource-list/optrpm:resource";
            }
          }
          
          leaf resource-type {
            description 
              "the type of resource, such as NE, board or termination
              point";
              
            config false;
            
            type identityref {
              base optrpm-types:resource-type;
            }
          }
          
          leaf admin-status {
            description
              "it is used to control the validity of threshold";
            type enumeration {
              enum enabled {
              description
                "if the admin-status of TCA configuration is enabled,
                the threshold is effective";
              }
        
              enum disabled {
                description
                  "if the admin-status of TCA configuration is 
                  disabled, the threshold is not effective";
              }
            }
          }
          
          uses tca-grouping;
        }
      }
    }
  }
  
  grouping tca-profile-grouping {
    description
      "grouping of TCA profile instance";
      
    leaf profile-id {
      description 
        "identifier of threshold crossing alerrt profile";
        
      type yang:uuid;    
    }
    
    leaf profile-name {
      description 
        "Name of the threshold crossing alerrt profile";
        
      type string;
    }
    
    container tca-cfg {
      description
        "detailed TCA configuration in a profile";
        
      list tca-indicator {
        description
          "list of TCA configuration.";
          
        key "indicator-name threshold-type period severity";
        uses tca-indicator-grouping;
      }    
    }
  }
  
  grouping tca-indicator-grouping {
    description
      "grouping for detail TCA configuration";
    leaf indicator-name {
      type string;
      description 
        "name of the indicator";
    }
    
    leaf indicator-value {
      mandatory true;
      type string;
      description 
        "treshold value of the indicator";
    }
    
    leaf indicator-value-unit {
      mandatory true;
      type string;
      description 
        "unit of indicator's value";
    }
    
    leaf threshold-type {
      description
        "it is used to indicate the trigger/clearing condition of 
        alert upon the threshold";
        
      type enumeration {
        enum upperbound-trigger {
          description
            "If the performace data exceeds this threshold value,
            a TCA will be triggered";
        }
        enum lowerbound-trigger {
          description
            "if the performace data is lower than this threshold
            value, a TCA will be triggered";
        }
        enum upperbound-clear {
          description
            "If the performance data is not longer bigger than this
            threshold value, the TCA triggered before will be cleared
            by system automatically";
        }
        enum lowerbound-clear {
          description
            "If the performance data is not longer lower than this
            threshold value, the TCA triggered before will be cleared
            by system automatically";
        }
      }
    }

    leaf period {
      description 
        "it is used to indicate the interval as per monitoring task";
        
      type identityref {
        base optrpm-types:period;
      }
    }
    
    leaf severity {
      description
        "it is used to indicate what severity level of alert would be
        triggered if not confirms to the threashold";
        
      type identityref {
        base optrpm-types:severity;
      }
    }
  }
  
  grouping tca-grouping {
    description
      "grouping of TCA configuration";
      
    container applied-profiles {
        description
          "Information of applied TCA profiles on this resource";
          
      list profile {
          description
            "list of applied TCA profile";
            
        key "profile-id";
        
        leaf profile-id {
          description
            "identifier of the applied TCA profile";
              
          type leafref {
            path "../../../../../optrpm:profiles/optrpm:profile" +
            "/optrpm:profile-id";
          }
        }
      }
    }
    container tca-cfg {
      description 
        "detailed configuration of TCA";
      list tca-indicator {
         description
           "list of tca indicator configuration";
        key "indicator-name threshold-type period severity";
        uses tca-indicator-grouping;
      }    
    }
  }
  

  rpc get-all-current-pm-data {
    description 
      "this RPC is used to retrieve current performance data.";
    
    input {
      leaf-list resources {
        description 
          "the identifier of resources from which current performace 
          data is collected";
          
        type leafref {
          path "/optrpm:performance-monitoring/optrpm:resources" + 
          "/optrpm:resource-list/optrpm:resource";
        }
      }
    }
    output {
      container pm-data {
        description 
          "result of current performance data";
          
        list pm-data-list {
          description 
            "list of curent performance data";
            
          key resource;
          uses pm-data-instance-grouping;
        }
      }      
    }
  }
  
  rpc get-historic-pm-data {
    input {
      description 
      "this RPC is used to retrieve historic performance data.";
      
      leaf-list resources {
        description
          "the identifier of resources from which historic performace 
          data is collected";
          
        type leafref {
          path "/optrpm:performance-monitoring/optrpm:resources" + 
          "/optrpm:resource-list/optrpm:resource";
        }
      }
      
      leaf start-time {
        description 
        "the starttime of performance data needed to be retrieved";
        
        type yang:date-and-time;
      }
      
      leaf end-time {
        description 
        "the endtime of performance data needed to be retrieved";
        
        type yang:date-and-time;
      }
    }
    output {
      container pm-data {
        description 
          "result of historic performance data";
          
        list pm-data-list {
          description 
            "list of historic performance data";
            
          key resource;
          uses pm-data-instance-grouping;
        }
      }      
    }
  }
  
  rpc clear-performance-monitoring-data {
    input {
      description 
        "This operation clears (reset) the PM registers for a list of 
        Measurement Points. Within the request for each Measurement 
        Point, it is possible to specify the granularity (15min, 24hr,
        NA) and location (nearEnd and/or farEnd and/or bidirectional) 
        for the PM registers that are to be reset.";
        
      leaf-list resources {
        description
          "the identifier of measurement points to clear PM data";
          
        type leafref {
          path "/optrpm:performance-monitoring/optrpm:resources" + 
          "/optrpm:resource-list/optrpm:resource";
        }
      }
    }
    output {
      leaf-list failed-resources {
        description
          "the identifier of measurement points which are failed to 
          clear PM data. An empty list indicates that the total 
          request was successful.";
          
        type leafref {
          path "/optrpm:performance-monitoring/optrpm:resources" + 
          "/optrpm:resource-list/optrpm:resource";
        }      
      }
    }
  }
  
  rpc get-profile-associated-termination-points {
    input {
      description 
        "This operation gets the set of TPs that are associated with 
        a TCA parameter profile.";
      
      leaf profile-id {
        description 
          "the identifier of profile which the client want to 
          retrieve";
          
        type leafref {
          path "/optrpm:performance-monitoring/optrpm:tca-management"
          + "/optrpm:profiles/optrpm:profile/optrpm:profile-id";
        }
      }
      
    }
    output {
      leaf-list resource-list {
        description
          "Provides the set of Resources associated with the profile 
          provided.";
          
        type leafref {
          path "/optrpm:performance-monitoring/optrpm:resources" + 
          "/optrpm:resource-list/optrpm:resource";
        }
      }
    }
  }
  
  
  grouping pm-data-instance-grouping {
    description 
      "grouping for common attributes of performance data";
      
    leaf resource {
    description 
      "the identifier of network resource which is monitored.";
    
      type leafref {
        path "/optrpm:performance-monitoring/optrpm:resources" + 
        "/optrpm:resource-list/optrpm:resource";
      }      
    }
    
    leaf collect-time {
      description 
        "the time of this data is collected";
        
      type yang:date-and-time;
    }
    
    leaf resource-type {
      description 
        "the type of resource, such as NE, board or port";
        
      type identityref {
        base optrpm-types:resource-type; 
      }      
    }
    
    container indicator-data {
      description 
        "grouping for historic performance data";
        
      list indicator-data-list {
        description 
          "list of historic performance data";
        key indicator-name;
        
        uses indicator-data-instance-grouping;
      }
    }
  }
  
  grouping indicator-data-instance-grouping {
    description 
      "grouping for a performance data";
      
    leaf indicator-name {
      description 
        "name of performance data indicator";
        
      type string;     
    }

    leaf indicator-value {
      description 
        "value of performance data";
        
      type string;
    }

    leaf indicator-value-unit {
      description 
        "unit of performance data value";
        
      type string;
    }
  }
  
}
